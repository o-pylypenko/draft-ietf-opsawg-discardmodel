module ietf-packet-discard-reporting-common {
  yang-version 1.1;
  namespace "urn:ietf:params:xml:ns:yang:"
          + "ietf-packet-discard-reporting-common";
  prefix pdr-common;

  import ietf-yang-types {
    prefix yang;
    reference
      "RFC 9911: Common YANG Data Types";
  }

  organization
    "IETF OPSAWG (Operations and Management Area Working Group)";
  contact
    "WG Web:   https://datatracker.ietf.org/wg/opsawg/
     WG List:  OPSAWG <mailto:opsawg@ietf.org>

     Editor:   John Evans
               <mailto:john@nopacketleftbehind.net>

     Editor:   Oleksandr Pylypenko
               <mailto:opylypenko@nvidia.com>

     Author:   Jeffrey Haas
               <mailto:jeffrey.haas@hpe.com>

     Author:   Aviran Kadosh
               <mailto:akadosh@cisco.com>

     Editor:   Mohamed Boucadair
               <mailto:mohamed.boucadair@orange.com>";
  description
    "This module defines a common YANG module for packet discard
     reporting.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-03-03 {
    description
      "Initial revision.";
    reference
      "RFC XXXX: Information and Data Models for Packet Discard
                 Reporting";
  }

  /*
   * Features
   */

  feature control-plane-stats {
    description
      "Indicates support of control plane discard statistics.";
  }

  feature interface-stats {
    description
      "Indicates support of interface discard statistics.";
  }

  feature flow-reporting {
    description
      "Indicates support of flow discard reporting.";
  }

  feature device-stats {
    description
      "Indicates support of global device discard statistics.";
  }

  /*
   * Identities
   */

  identity direction {
    description
      "Defines a direction for the reported statistics.";
  }

  identity ingress {
    base direction;
    description
      "Reports statistics for the received packets from
       the network.";
  }

  identity egress {
    base direction;
    description
      "Reports statistics for the sent packets to
       the network.";
  }

  identity address-family {
    description
      "Defines a type for the address family.

       This identity is defined here rather than importing
       it from other YANG modules to simplify implementations
       and avoid inheriting dependencies of those modules.

       Additional address families can be added by defining
       identities derived from this base identity, without
       affecting existing implementations.";
  }

  identity ip {
    base address-family;
    description
      "Identity for IP address family.";
  }

  identity ipv4 {
    base ip;
    description
      "Identity for IPv4 address family.";
  }

  identity ipv6 {
    base ip;
    description
      "Identity for IPv6 address family.";
  }

  identity no-buffer-type {
    description
      "Defines a type for congestion-related discards.";
  }

  identity aqm {
    base no-buffer-type;
    description
      "Indicates a discard due to an Active Queue Management (AQM)
       algorithm.";
  }

  identity tail-drop {
    base no-buffer-type;
    description
      "Indicates a discard due to tail drop.";
  }

  /*
   * Groupings
   */

  grouping basic-packets {
    description
      "Grouping for packet counters.";
    leaf packets {
      type yang:counter64;
      description
        "Number of packets.";
    }
  }

  grouping basic-packets-bytes {
    description
      "Grouping for packet and byte counters.";
    uses basic-packets;
    leaf bytes {
      type yang:counter64;
      description
        "Number of bytes.";
    }
  }

  grouping basic-frames {
    description
      "Grouping for Layer 2 frame counters.";
    leaf frames {
      type yang:counter64;
      description
        "Number of Layer 2 frames.";
    }
  }

  grouping l2-traffic {
    description
      "Grouping for Layer 2 frame and byte counters.";
    uses basic-frames;
    leaf bytes {
      type yang:counter64;
      description
        "Number of Layer 2 bytes.";
    }
  }

  grouping l3-traffic {
    description
      "Layer 3 traffic counters per address family.";
    list address-family-stat {
      key "address-family";
      description
        "Reports per address family traffic counters.";
      leaf address-family {
        type identityref {
          base address-family;
        }
        description
          "Specifies an address family.";
      }
      uses basic-packets-bytes;
      container unicast {
        description
          "Unicast traffic counters.";
        uses basic-packets-bytes;
      }
      container multicast {
        description
          "Multicast traffic counters.";
        uses basic-packets-bytes;
      }
      container broadcast {
        when "derived-from-or-self(../address-family, "
           + "'pdr-common:ipv4')" {
          description
            "Only applicable for IPv4.";
        }
        description
          "Broadcast traffic counters.";
        uses basic-packets-bytes;
      }
    }
  }

  grouping class-list {
    description
      "Class-based traffic counters.";
    list class {
      key "id";
      min-elements 1;
      description
        "Class traffic counters.";
      leaf id {
        type string;
        description
          "Indicates a Quality of Service (QoS) class
           identifier.";
      }
      uses basic-packets-bytes;
    }
  }

  grouping qos {
    description
      "QoS traffic counters.";
    container qos {
      presence "QoS statistics are available.";
      description
        "Per-class QoS traffic counters.";
      uses class-list;
    }
  }

  grouping no-buffer-qos {
    description
      "QoS discard counters.";
    container qos {
      presence "QoS statistics are available.";
      description
        "Per-class QoS traffic counters.";
      list class {
        key "id";
        min-elements 1;
        description
          "Class traffic counters.";
        leaf id {
          type string;
          description
            "Indicates a QoS class identifier.";
        }
        uses basic-packets-bytes;
        list discard-type {
          key "type";
          description
            "Per-type discard counters.";
          leaf type {
            type identityref {
              base no-buffer-type;
            }
            description
              "Specifies the discard type.";
          }
          uses basic-packets-bytes;
        }
      }
    }
  }

  grouping traffic {
    description
      "All traffic counters.";
    container l2 {
      description
        "Layer 2 traffic counters.";
      uses l2-traffic;
    }
    container l3 {
      description
        "Layer 3 traffic counters.";
      uses l3-traffic;
    }
    uses qos;
  }

  grouping errors-l2-rx {
    description
      "Layer 2 ingress frame error discard counters.";
    container rx {
      description
        "Layer 2 ingress frame receive error discard
         counters.";
      leaf frames {
        type yang:counter64;
        description
          "The number of frames discarded due to errors
           with the received frame.";
      }
      leaf crc-error {
        type yang:counter64;
        description
          "The number of received frames discarded due to
            Cyclic Redundancy Check (CRC) error.";
      }
      leaf invalid-mac {
        type yang:counter64;
        description
          "The number of received frames discarded due to
           an invalid Media Access Control (MAC) address.
           Applies to Ethernet or Ethernet-derived
           encapsulations where MAC addresses are present.";
      }
      leaf invalid-vlan {
        type yang:counter64;
        description
          "The number of received frames discarded due to
           an invalid VLAN tag. Applies to Ethernet or
           Ethernet-derived encapsulations where VLAN tags
           are present.";
      }
      leaf invalid-frame {
        type yang:counter64;
        description
          "The number of invalid received frames discarded due to
           other reasons, not limited to: malformed frames,
           frame-size violations.";
      }
    }
  }

  grouping errors-l3 {
    description
      "Layer 3 packet error discard counters.";
    container rx {
      description
        "Counters for Layer 3 packets discarded due to errors
         in the received packet, indicating an upstream problem
         rather than an issue with the reporting device.";
      leaf packets {
        type yang:counter64;
        description
          "The number of Layer 3 packets discarded due to
           errors in the received packet.";
      }
      leaf checksum-error {
        type yang:counter64;
        description
          "Reports IPv4 packets discarded because validation of the
           IPv4 header checksum failed.

           This counter is applicable only to IPv4 packets. IPv6 does
           not include an internet-layer header checksum, so IPv6
           packets are not reported under this counter.";
      }
      leaf invalid-packet {
        type yang:counter64;
        description
          "The number of received invalid packets discarded due
           to other reasons, not limited to: invalid packet length,
           invalid header fields, invalid options, invalid protocol
           version, invalid flags or control bits, malformed
           packets.";
      }
    }
    container mtu-exceeded {
      description
        "Counters for packets discarded because their size exceeded
         the applicable Maximum Transmission Unit (MTU).";
      leaf packets {
        type yang:counter64;
        description
          "The total number of packets discarded because their size
           exceeded the applicable MTU.  This includes packets
           reported by the more specific counters in this
           container.";
      }
      leaf fragmentation-not-permitted {
        type yang:counter64;
        description
          "The number of packets discarded because the packet size
           exceeded the applicable MTU and the forwarding node was
           not permitted to fragment the packet.  This includes IPv4
           packets with the Don't Fragment (DF) bit set and IPv6
           packets, which forwarding nodes do not fragment.";
      }
      leaf fragmentation-permitted-not-performed {
        type yang:counter64;
        description
          "The number of packets discarded because the packet size
           exceeded the applicable MTU, fragmentation was permitted
           in principle, but the packet was not fragmented and
           forwarded.  This includes IPv4 packets with the DF bit
           clear.";
      }
      reference
        "RFC 791: Internet Protocol, Sections 3.1 and 3.2
         RFC 8200: Internet Protocol, Version 6 (IPv6)
                   Specification, Sections 4.5 and 5";
    }
    leaf ttl-expired {
      type yang:counter64;
      description
        "The number of packets discarded because the TTL
         (IPv4 or MPLS) expired or the Hop Limit (IPv6)
         was exceeded.";
    }
    leaf no-route {
      type yang:counter64;
      description
        "The number of received packets discarded because the
         destination address does not match a valid entry in the
         routing table. This includes packets discarded after
         outer header removal (e.g., MPLS label disposition or
         tunnel decapsulation) when the exposed IP header does
         not match a valid entry in the routing table. MPLS label
         lookup failures are reported under 'invalid-label'.";
    }
    leaf neighbor-resolution-failure {
      type yang:counter64;
      description
        "Reports packets discarded because the forwarding engine
         could not resolve or use the link-layer adjacency required
         to forward the packet to the selected next hop.

         This includes packets dropped because ARP resolution for an
         IPv4 next hop failed, Neighbor Discovery resolution for an
         IPv6 next hop failed, or the resolved neighbor entry was
         unusable according to local neighbor state.

         This counter applies when route selection identified a next
         hop, but forwarding could not complete because the required
         neighbor or adjacency information was unavailable or
         unusable. Packets discarded because no route matched
         the destination are reported under 'no-route'. Packets
         discarded due to internal device faults are reported
         under 'internal'.";
      reference
        "RFC 826: An Ethernet Address Resolution Protocol -- or --
                  Converting Network Protocol Addresses to 48.bit
                  Ethernet Address for Transmission on Ethernet
                  Hardware
         RFC 4861: Neighbor Discovery for IP version 6 (IPv6)";
    }
    leaf invalid-sid {
      type yang:counter64;
      description
        "The number of received packets discarded due to an
         invalid Segment Routing over IPv6 (SRv6) segment
         identifier (SID).
         This counter is incremented only by the node processing
         the SID (i.e., where the packet's destination address
         matches a locally instantiated SID); transit nodes that
         forward the packet without processing the SRH do not
         increment it. Discards of SRv6 packets whose
         destination address does not match a valid route are
         reported under 'no-route'.
         For SR-MPLS, SID lookup failures are reported under
         'invalid-label'.";
      reference
        "RFC 8402: Segment Routing Architecture
         RFC 8660: Segment Routing with the MPLS Data Plane
         RFC 8754: IPv6 Segment Routing Header (SRH)
         RFC 8986: Segment Routing over IPv6 (SRv6) Network
                   Programming";
    }
    leaf invalid-label {
      type yang:counter64;
      description
        "The number of received packets discarded because the
         top MPLS label does not match a valid Incoming Label
         Map (ILM) entry. This is the MPLS equivalent of
         'no-route'.";
      reference
        "RFC 3031: Multiprotocol Label Switching Architecture,
         Section 3.18";
    }
  }

  grouping errors-l3-int {
    description
      "Internal error discard counters.";
    leaf packets {
      type yang:counter64;
      description
        "The number of packets discarded due to internal
         errors.";
    }
    leaf parity-error {
      type yang:counter64;
      description
        "The number of packets discarded due to parity
         errors, which typically mean that the ASIC
         detected corruption in an internal memory, table,
         buffer, or metadata structure used while processing
         the packet, and dropped the packet rather than
         forwarding it using potentially bad state.";
    }
  }

  grouping errors-l2-tx {
    description
      "Layer 2 transmit error discard counters.";
    container tx {
      description
        "Layer 2 transmit frame error discard counters.";
      leaf frames {
        type yang:counter64;
        description
          "The number of Layer 2 frames discarded due to
           errors when transmitting.";
      }
    }
  }

  grouping errors-l3-tx {
    description
      "Layer 3 transmit error discard counters.";
    container tx {
      description
        "Layer 3 transmit packet error discard counters.";
      leaf packets {
        type yang:counter64;
        description
          "The number of Layer 3 packets discarded due to
           errors when transmitting.";
      }
    }
  }

  grouping errors {
    description
      "Error discard counters.";
    container l2 {
      description
        "Layer 2 frame error discard counters.";
      uses errors-l2-rx;
      uses errors-l2-tx;
    }
    container l3 {
      description
        "Layer 3 packet error discard counters.";
      uses errors-l3;
      uses errors-l3-tx;
    }
    container internal {
      description
        "Internal error discard counters.";
      uses errors-l3-int;
    }
  }

  grouping policy-l2 {
    description
      "Layer 2 policy frame discard counters.";
    leaf frames {
      type yang:counter64;
      description
        "The number of Layer 2 frames discarded due
         to policy.";
    }
    leaf acl {
      type yang:counter64;
      description
        "The number of frames discarded due to Layer 2
         Access Control Lists (ACLs).";
    }
  }

  grouping policy-l3 {
    description
      "Layer 3 policy packet discard counters.";
    leaf packets {
      type yang:counter64;
      description
        "The number of Layer 3 packets discarded due to policy.";
    }
    leaf acl {
      type yang:counter64;
      description
        "The number of packets discarded due to Layer 3
         (and higher layers) ACLs.";
    }
    container policer {
      description
        "Counters for packets discarded due to policer
         violations.";
      uses basic-packets-bytes;
      container classes {
        presence "Per-class policer statistics are available.";
        description
          "Per-class policer discard counters.";
        uses class-list;
      }
    }
    leaf null-route {
      type yang:counter64;
      description
        "The number of packets discarded due to matching
         a null route.";
    }
    leaf rpf {
      type yang:counter64;
      description
        "The number of packets discarded due to failing
         Reverse Path Forwarding (RPF) check.";
    }
    leaf dos {
      type yang:counter64;
      description
        "The number of packets discarded by dedicated
         Denial-of-Service (DoS) protection mechanisms, such as
         implementation-specific heuristics that identify and discard
         DoS traffic.

         Where a DoS attack is mitigated using an ACL or a null
         route, those discards are reported under 'acl' or
         'null-route' respectively, not under this counter, since
         the association with DoS mitigation is known only to the
         operator.";
    }
  }

  grouping discards {
    description
      "Discard counters.";
    container l2 {
      description
        "Layer 2 frame discard counters.";
      uses l2-traffic;
    }
    container l3 {
      description
        "Layer 3 packet discard counters.";
      uses l3-traffic;
    }
    container errors {
      description
        "Error discard counters.";
      uses errors;
    }
    container policy {
      description
        "Policy-related discard counters.";
      uses policy;
    }
    container no-buffer {
      description
        "Congestion-related discard counters.";
      uses no-buffer-qos;
    }
  }

  grouping policy {
    description
      "Policy-related discard counters.";
    container l2 {
      description
        "Layer 2 policy frame discard counters.";
      uses policy-l2;
    }
    container l3 {
      description
        "Layer 3 policy packet discard counters.";
      uses policy-l3;
    }
  }

  grouping traffic-and-discards {
    description
      "Specifies overall traffic and discard counters.";
    container traffic {
      description
        "Traffic counters.";
      uses traffic;
    }
    container discards {
      description
        "Discard counters.";
      uses discards;
    }
  }

  grouping interface {
    description
      "Interface-level traffic and discard counters.";
    list traffic {
      key "direction";
      description
        "Traffic counters.";
      leaf direction {
        type identityref {
          base direction;
        }
        description
          "Specifies a direction.";
      }
      uses traffic;
    }
    list discards {
      key "direction";
      description
        "Discard counters.";
      leaf direction {
        type identityref {
          base direction;
        }
        description
          "Specifies a direction.";
      }
      uses discards;
    }
  }

  grouping control-plane {
    description
      "Control plane packet counters.";
    list traffic {
      key "direction";
      description
        "Total control plane packets.";
      leaf direction {
        type identityref {
          base direction;
        }
        description
          "Specifies a direction.";
      }
      uses basic-packets-bytes;
    }
    list discards {
      key "direction";
      description
        "Control plane packet discard counters.";
      leaf direction {
        type identityref {
          base direction;
        }
        description
          "Specifies a direction.";
      }
      uses basic-packets-bytes;
      container policy {
        description
          "Number of control plane packets discarded due to policy.";
        uses basic-packets;
      }
    }
  }
}
